"""
Input arguments are chained together,
applied (in sequence) to a STEP file
and then the output is saved (to the same file!)
use the 'tmp' command to write the output file with a "tmp_" prefix

usage:
(If freecad.exe is in PATH):
freecad.exe stepfile.STEP adjust.FCMacro [arg1] [arg2] [arg3] ... [argn]

arguments:

Rotational - rotte the component 90degrees around the origin (0,0,0)
rx+ (rotate +90 degrees around X axis)
rx- (rotate -90 degrees around X axis)
ry+ (rotate +90 degrees around Y axis)
ry- (rotate -90 degrees around Y axis)
rz+ (rotate +90 degrees around Z axis)
rz- (rotate -90 degrees around Z axis)

Alignment - align one of the sides of the part with the origin
ax+ (align right side of part with yz plane)
ax- (align left side of part with yz plane)
ax  (align center of part with yz plane)
ay+ (align top side of part with xz plane)
ay- (align bottom side of part with xz plane)
ay  (align center of part with xz plane)
az+ (align top side of part with xy plane)
az- (align bottom side of part with xy plane)
az  (align center of part with xy plane)

Movement - move the part along a given axis
mx=<d> (move part along x-axis by d)
my=<d> (move part along y-axis by d)
mz=<d> (move part along z-axis by d)

Scaling - scale the part by the given value
s=<d> (scale part by d)

Pin Alignment - Assuming part is centered, offset the part such that pin-1 is at 0 
p=x (align p1 along x axis)
p=y (align p1 along y axis)
p=z (align p1 along z axis)

"""

import FreeCAD, FreeCADGui
from stepup import *

FreeCADGui.ActiveDocument.ActiveView.setAxisCross(True)

objs = getAllObjects()[0:1] #only operate on the first object

removeAllButFirst()

for i in sys.argv[2:]:

    i = i.lower()
    
    #rotation
    if i.startswith('r') and len(i) == 3:
        
        axis = i[1]
        sign = i[2]
            
        if axis not in ['x','y','z']:
            sayerr(i,"does not contain valid axis")
            continue
        
        if sign not in ['+','-']:
            sayerr(i,"does not contain valid sign")
            continue
        
        if sign == '+': 
            angle =  90.0
        else:
            angle = -90.0
            
        say("Rotating",axis,angle)
        if axis == 'x':
            rotate(objs,angle,(1,0,0))
        elif axis == 'y':
            rotate(objs,angle,(0,1,0))
        elif axis == 'z':
            rotate(objs,angle,(0,0,1))
                
    #alignment
    elif i.startswith('a') and len(i) in [2,3]:
        axis = i[1]
        
        if axis not in ['x','y','z']:
            sayerr(i,"does not contain valid axis")
            continue
            
        if len(i) == 2:
            sign = ""
        else:
            sign = i[2]
            
        if sign not in ['','+','-']:
            sayerr(i,"does not contain valid sign")
            continue
            
        if axis == 'x':
            if sign == '':
                say("Aligning X Middle")
                alignXMid(objs)
            elif sign == '+':
                say("Aligning X Right")
                alignXMax(objs)
            else:
                say("Aligning X Left")
                alignXMin(objs)
            
        elif axis == 'y':
            if sign == '':
                say("Aligning Y Middle")
                alignYMid(objs)
            elif sign == '+':
                say("Aligning Y Top")
                alignYMax(objs)
            else:
                say("Aligning Y Bottom")
                alignYMin(objs)
            
        elif axis == 'z':
            if sign == '':
                say("Aligning Z Middle")
                alignZMid(objs)
            elif sign == '+':
                say("Aligning Z Top")
                alignZMax(objs)
            else:
                say("Aligning Z Bottom")
                alignZMin(objs)
                
    #Movement
    elif i.startswith("m") and len(i.split("=")) == 2:
        
        arg,d = i.split("=")
        
        if len(arg) == 2:
            axis = arg[1]
        else:
            sayerr(i,"axis not supplied")
            continue
            
        if axis not in ['x','y','z']:
            sayerr(i,"contains invalid axis")
            continue
         
        #make sure we have a valid number
        try:
            distance = float(d)
        except:
            sayerr(i,"does not contain a valid distance")
            continue
            
        #ok, now we can move
        x,y,z = 0,0,0
        
        if axis == 'x':
            x = distance
        elif axis == 'y':
            y = distance
        elif axis == 'z':
            z = distance
            
        say("Moving:",axis,distance)
        
        move(objs,x,y,z)
        
    #pin alignment
    elif i.startswith("p") and len(i.split("=")) == 2:
        axis = i.split("=")[1]
        if axis not in ['x','y','z']:
            sayerr(i,"contains invalid axis")
            
        say('Aligning pin-1 on',axis,'axis')
            
        #extract pin information
        d = getPinOffset(getStepFile())
        say("Moving on",axis,"axis by",d)
            
        if axis == 'x':
            alignXMid(objs)
            move(objs,d,0,0)
        elif axis == 'y':
            alignYMid(objs)
            move(objs,0,d,0)
        else:
            alignZMid(objs)
            move(objs,0,0,d)
        
    #scaling
    elif i.startswith("s") and len(i.split("=")) == 2:
        scaling = i.split("=")[1]
        
        try:
            scaling = float(scaling)
        except:
            sayerr(i,"does not contain a valid scaling factor")
            continue
            
        scale(objs,scaling)
        
    elif i.endswith(".fcmacro"):
        pass
    
    elif i.endswith(".step"):
        pass
    
    elif i.endswith(".stp"):
        pass
         
    #tmp is a signal to FreeCAD, so ignore
    elif i == 'tmp':
        pass
         
    else:
        sayerr(i,"is not a valid argument")
        
FreeCADGui.ActiveDocument.ActiveView.setAxisCross(True)

if 'tmp' not in sys.argv:
    exportStep(objs,getStepFile())
    exit()
else:
    exportStep(objs,getTempStepFile())
