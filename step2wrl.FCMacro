"""
Take a STEP or STP input file,
Scale it by 1/2.54
Export a .wrl file (with colors!)
"""

import sys
import freecad

step = freecad.getStepFile().lower()

freecad.say("Importing:",step)

if not step.endswith("step") and not step.endswith("stp"):
    freecad.sayerr("STEP file must be supplied")
    
wrl = freecad.getWRLFile()
freecad.say("Exporting:",wrl)

#convert to the silly KiCAD inches format
freecad.scale(freecad.getAllObjects(),1.0/2.54)

freecad.exportVRMLMeshes(freecad.getAllMeshes(),wrl)
exit()
